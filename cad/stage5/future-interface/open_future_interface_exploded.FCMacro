import os
import FreeCAD as App
import FreeCADGui as Gui

folder = os.path.dirname(__file__)
doc = App.openDocument(os.path.join(folder, 'SCCI_RH_future_interface_exploded.FCStd'))
for obj in doc.Objects:
    if 'DisplayColor' in obj.PropertiesList:
        obj.ViewObject.ShapeColor = tuple(obj.DisplayColor)[:3]
        if 'Allocation' in obj.Name:
            obj.ViewObject.Transparency = 55
Gui.activeDocument().activeView().viewAxonometric()
Gui.activeDocument().activeView().fitAll()
